' ============================================================================
' RunExportNodeDataToExcelForSelectRuns.CATScript
'
' CATIA V5 CATScript
'
' Exports node coordinates and bend radii from selected Arrangement Runs
' to Microsoft Excel.
'
' The output structure is based on the node-data format used by
' CATIA V5 "Routing with Defined Nodes".
'
' Version: 1.0
' ============================================================================

Sub CATMain()

    Dim oDocument As Product
    Dim oProduct As Product
    Dim arrPrd As ArrangementProduct
    Dim arrRuns As ArrangementRuns
    Dim arrRun1 As ArrangementRun
    Dim oArrNodes As ArrangementNodes

    Set oDocument = CATIA.ActiveDocument

    ' Проверка, что что-то выделено в документе
    If oDocument.Selection.Count = 0 Then
        MsgBox "Ничего не выделено в документе", vbExclamation
        Exit Sub
    End If

    Set oProduct = oDocument.Product
    Set arrPrd = oProduct.GetTechnologicalObject("ArrangementProduct")
    Set arrRuns = arrPrd.ArrangementRuns

    ' Создание объекта Excel
    Dim ExcelApp As Object
    Set ExcelApp = CreateObject("Excel.Application")
    ExcelApp.Visible = True

    ' Создание новой книги
    Dim ExcelWorkbook As Object
    Set ExcelWorkbook = ExcelApp.Workbooks.Add

    ' Выбор первого листа в книге
    Dim ExcelSheet As Object
    Set ExcelSheet = ExcelWorkbook.Worksheets(1)

    ' Запись заголовков
    ExcelSheet.Cells(1, 1).Value = "NodeNum"
    ExcelSheet.Cells(1, 2).Value = "X-coord"
    ExcelSheet.Cells(1, 3).Value = "Y-coord"
    ExcelSheet.Cells(1, 4).Value = "Z-coord"
    ExcelSheet.Cells(1, 5).Value = "Bend radius"

    ' Переменная для отслеживания текущей строки в Excel
    Dim currentRow As Integer
    currentRow = 2 ' Начинаем с 2, так как 1 строка занята заголовками

    ' Перебор всех узлов и запись данных в Excel
    Dim iRelAxis As Move
    Set iRelAxis = oDocument.Product.Move
    Dim dblCoords(3) As Double

    ' Перебор всех выделенных элементов
    For j = 1 To oDocument.Selection.Count

        ' Получение имени текущего выделенного элемента
        Dim selectedElementName As String
        selectedElementName = oDocument.Selection.Item(j).Value.Name

        ' Проверка содержит ли имя или номер детали подстроку "Run"
        If InStr(1, selectedElementName, "Run", vbTextCompare) > 0 Then

             On Error Resume Next
             ' Получение объекта ArrangementRun
             Set arrRun1 = arrRuns.Item(selectedElementName)
             If Err.Number <> 0 Then
             		MsgBox "Откройте новое окно сборки в которой находятся выделяемые Run'ы и повторите попытку", vbExclamation
             		Err.Clear
             		Exit Sub
             End If

            ' Получение объекта ArrangementNodes
            Set oArrNodes = arrRun1.ArrangementNodes

            ' Перебор всех узлов и запись данных в Excel
            For i = 1 To oArrNodes.Count
                ' Получение текущего узла
                Dim currentNode As ArrangementNode
                Set currentNode = oArrNodes.Item(i)

                ' Получение координат точки узла
                currentNode.GetPoint iRelAxis, dblCoords

                ' Получение радиуса гиба точки узла
                Dim dblBendRadius As Double
                dblBendRadius = currentNode.BendRadius

                ' Запись данных в Excel
                ExcelSheet.Cells(currentRow, 1).Value = i
                ExcelSheet.Cells(currentRow, 2).Value = dblCoords(0) & "mm"
                ExcelSheet.Cells(currentRow, 3).Value = dblCoords(1) & "mm"
                ExcelSheet.Cells(currentRow, 4).Value = dblCoords(2) & "mm"
                ExcelSheet.Cells(currentRow, 5).Value = dblBendRadius & "mm"

                ' Увеличение переменной текущей строки
                currentRow = currentRow + 1
            Next
        End If

    Next

    ' Освобождение ресурсов Excel
    Set ExcelSheet = Nothing
    Set ExcelWorkbook = Nothing
    Set ExcelApp = Nothing

End Sub
