Sub CATMain()

    Dim oDocument As Product
    Dim oProduct As Product
    Dim arrPrd As ArrangementProduct
    Dim arrRuns As ArrangementRuns
    Dim arrRun1 As ArrangementRun
    Dim oArrNodes As ArrangementNodes

    Set oDocument = CATIA.ActiveDocument

    ' Проверка, что что-то выделено в документе
    If oDocument.Selection.Count = 0 Then
        MsgBox "Ничего не выделено в документе", vbExclamation
        Exit Sub
    End If

    Set oProduct = oDocument.Product
    Set arrPrd = oProduct.GetTechnologicalObject("ArrangementProduct")
    Set arrRuns = arrPrd.ArrangementRuns

    ' Создание объекта Excel
    Dim ExcelApp As Object
    Set ExcelApp = CreateObject("Excel.Application")
    ExcelApp.Visible = True

    ' Создание новой книги
    Dim ExcelWorkbook As Object
    Set ExcelWorkbook = ExcelApp.Workbooks.Add

    ' Выбор первого листа в книге
    Dim ExcelSheet As Object
    Set ExcelSheet = ExcelWorkbook.Worksheets(1)

    ' Запись заголовков
    ExcelSheet.Cells(1, 1).Value = "NodeNum"
    ExcelSheet.Cells(1, 2).Value = "X-coord"
    ExcelSheet.Cells(1, 3).Value = "Y-coord"
    ExcelSheet.Cells(1, 4).Value = "Z-coord"
    ExcelSheet.Cells(1, 5).Value = "Bend radius"
    ExcelSheet.Cells(1, 6).Value = "Bend angle"
    ExcelSheet.Cells(1, 7).Value = "Instance Name"
    ExcelSheet.Cells(1, 8).Value = "Part Number"
    ExcelSheet.Cells(1, 9).Value = "Run Length"
    ExcelSheet.Cells(1, 10).Value = "Section Type"
    ExcelSheet.Cells(1, 11).Value = "Section Diameter"
    ExcelSheet.Cells(1, 12).Value = "Section Height"
    ExcelSheet.Cells(1, 13).Value = "Section Width"
    ExcelSheet.Cells(1, 14).Value = "Area, m^2"

    ' Применение фильтра
    ExcelSheet.Range("A1:N1").AutoFilter

    ' Переменная для отслеживания текущей строки в Excel
    Dim currentRow As Integer
    currentRow = 2 ' Начинаем с 2, так как 1 строка занята заголовками

    ' Перебор всех узлов и запись данных в Excel
    Dim iRelAxis As Move
    Set iRelAxis = oDocument.Product.Move
    Dim dblCoords(3) As Double

    ' Перебор всех выделенных элементов
    For j = 1 To oDocument.Selection.Count

        ' Получение Part Number текущего выделенного элемента
        Dim selectedElementPartNumber As String
        selectedElementPartNumber = oDocument.Selection.Item(j).Value.PartNumber

        ' Получение имени текущего выделенного элемента
        Dim selectedElementName As String
        selectedElementName = oDocument.Selection.Item(j).Value.Name

        ' Проверка содержит ли имя или номер детали подстроку "Run"
        If InStr(1, selectedElementName, "Run", vbTextCompare) > 0 Then

             On Error Resume Next
             ' Получение объекта ArrangementRun
             Set arrRun1 = arrRuns.Item(selectedElementName)
             If Err.Number <> 0 Then
             		MsgBox "Откройте новое окно сборки в которой находятся выделяемые Run'ы и повторите попытку", vbExclamation
             		Err.Clear
             		Exit Sub
             End If

            ' Получение объекта ArrangementNodes
            Set oArrNodes = arrRun1.ArrangementNodes

            ' Получение длины Run
            Dim dblRunLength As Double
            dblRunLength = arrRun1.Length
            
            ' Получение типа Run
            Dim strSectionType As String
            Dim dblSectionDia As Double
            Dim dblSectionHeight As Double
            Dim dblSectionWidth As Double
            If arrRun1.SectionType=1 Then
            	strSectionType = "Rectangular"
              dblSectionHeight = arrRun1.SectionHeight
              dblSectionWidth = arrRun1.SectionWidth
              dblSectionDia = (4 * dblSectionHeight * dblSectionWidth / 3.14)^0.5
            Else
            	strSectionType = "Round"
              dblSectionDia = arrRun1.SectionDiameter
              dblSectionHeight = ""
              dblSectionWidth = ""
            End If

            Dim dblSectionArea As Double
            If arrRun1.SectionType=1 Then
            	strSectionType = "Rectangular"
              dblSectionArea = dblSectionHeight * dblSectionWidth * 0.000001
            Else
            	strSectionType = "Round"
              dblSectionArea = 3.14 * dblSectionDia^2 / 4 * 0.000001
            End If

            ' Перебор всех узлов и запись данных в Excel
            For i = 1 To oArrNodes.Count

                ' Получение текущего узла
                Dim currentNode As ArrangementNode
                Set currentNode = oArrNodes.Item(i)

                ' Получение координат точки узла
                currentNode.GetPoint iRelAxis, dblCoords

                ' Получение радиуса гиба точки узла
                Dim dblBendRadius As Double
                dblBendRadius = currentNode.BendRadius

                ' Получение угла гиба точки узла
                Dim dblBendAngle As Double
                If i = 1 or i = oArrNodes.Count Then
                	dblBendAngle = "Edge"
                Else
                	dblBendAngle = currentNode.BendAngle
                End If

                ' Запись данных в Excel
                ExcelSheet.Cells(currentRow, 1).Value = i
                ExcelSheet.Cells(currentRow, 2).Value = dblCoords(0)
                ExcelSheet.Cells(currentRow, 3).Value = dblCoords(1)
                ExcelSheet.Cells(currentRow, 4).Value = dblCoords(2)
                ExcelSheet.Cells(currentRow, 5).Value = dblBendRadius
                ExcelSheet.Cells(currentRow, 6).Value = dblBendAngle
                ExcelSheet.Cells(currentRow, 7).Value = selectedElementName
                ExcelSheet.Cells(currentRow, 8).Value = selectedElementPartNumber
                ExcelSheet.Cells(currentRow, 9).Value = dblRunLength
                ExcelSheet.Cells(currentRow, 10).Value = strSectionType
                ExcelSheet.Cells(currentRow, 11).Value = dblSectionDia
                ExcelSheet.Cells(currentRow, 12).Value = dblSectionHeight
                ExcelSheet.Cells(currentRow, 13).Value = dblSectionWidth
                ExcelSheet.Cells(currentRow, 14).Value = dblSectionArea


                ' Увеличение переменной текущей строки
                currentRow = currentRow + 1
            Next
        End If

    Next

    ' Освобождение ресурсов Excel
    Set ExcelSheet = Nothing
    Set ExcelWorkbook = Nothing
    Set ExcelApp = Nothing

End Sub
